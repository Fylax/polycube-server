module helloworld {
  yang-version 1.1;
  namespace "http://polycube.network/helloworld";
  prefix "helloworld";

  import polycube-base { prefix "basemodel"; }

  organization "Polycube open source project";
   description "YANG data model for the Polycube Helloworld service";
  
  basemodel:service-description "Helloworld Service";
  basemodel:service-version "2.0";
  basemodel:service-name "helloworld";
  basemodel:service-min-kernel-version "4.14.0";

  uses "basemodel:base-yang-module";

  leaf action {
    type enumeration {
      enum DROP;
      enum SLOWPATH;
      enum FORWARD;
    }
    default DROP;
    description "Action performed on the received packet (i.e., DROP, SLOWPATH, or FORWARD; default: DROP)";
  }
}
